#usage "<b>Resistance and Peak Current Calculator for Conductive Ink</b>\n"
       "<p>"
       "This Creates a list of all signals of a board, together "
       "with their length, area, resistance, minimum and maximum "
       "width and maximum current."
       "<p>"
       "Unlike length-freq-ri.ulp, this calculation leaves out "
       "frequency, but calculates resistance correctly using all "
       "traces in the signal."

       "<p>"
       "Parallel tracks and polygons are not taken into consideration."
       "<p>"
       "<author>Author: support@voltera.io</author>"

// THIS PROGRAM IS PROVIDED AS IS AND WITHOUT WARRANTY OF ANY KIND, EXPRESSED OR IMPLIED

// --------------------------------------- CONSTANTS

string Help = usage;
string HButton = "&Help";
string SButton = "&Save";

real f, wire_length_total, res_total_ink, res_total_cu;
int index[];

    // ** aus "Mechanik der Elektronik"
    // mm  <1  1  2  3  4  5  6  7  8  9 10 11 12 13 mm Leiterbreite bei 35 um Cu

// Leave this in for now, but make a new method for ink.
real k[] = { 9, 8.8, 6, 4, 3.2, 2.9, 2.9, 2.9, 2.9, 2.9, 2.9, 2.9, 2.9, 2.9, 2.9 };

    //               _______________________
    //  Imax ~ 5.25 V [d x b x (d + b)] x k      ||  (tL ~60°)
    //
    //  d = um Cu-Kaschierung
    //  b = Breite mm
    //  k = Korrekturwert aus Tabelle      02.02.2000 alf
    //  ** aus "Mechanik der Elektronik"

real Cu = 0.035;  // 35 um cu thickness 1oz
real Ink = 0.085; // 85 um standard ink thickness


real wire_length[], width_min[], width_max[], resistance_ink[], resistance_copper[];

string signal[];

real c = 299800;   // Speed of light in vacuum [km/s] - for frequency calcualtion, which is currently not possible

int n = 0;
int t;
string data[];
string h;
string header;
int note = 0;

// --------------------------------------- METHODS

void help(void) {
  dlgMessageBox(Help, "Ok");
  return;
}

void dialog(void)
{
  int select = 0;
  int Result = dlgDialog("Resistance and Peak Current Calculator for Conductive Ink") {
    dlgLabel(header);
    string lab;
    sprintf(lab, " Ink thickness = %.3f mm \n Ink tRef = 80C", Ink);
    dlgLabel(lab);
    dlgListView("", data, select);
    // dlgHBoxLayout {
    //     dlgLabel
    // }
    dlgStretch(0);
    dlgHBoxLayout {
      dlgStretch(1);
      dlgPushButton("+&Save") {
        board(B) {
          string FileName = dlgFileSave("Save list", filesetext(B.name, ".txt"));
          if (FileName) {
             output (FileName, "wt") {
               printf("%s", header);
               for (int x = 0; x < t; x++)
                   printf("%s\n", data[x]);
               if (note) {
                  sprintf( h, "\n ***  note wire width.\n");
                  data[t]  += h;
                  t++;
                  }
               }
             }
          }
        }
      dlgPushButton("-Close") dlgReject();
      }
    };
  if (!Result)
     exit(0);
}

real WireLength(real x1, real x2, real y1, real y2)
{
  return sqrt(pow(x2 - x1, 2) + pow(y2 - y1, 2));
}

real ArcLength(real ang1, real ang2, real radius)
{
  return radius  * 2 * PI / 360 * (ang2 - ang1);
}

real Frequency(real c, real l)
{
  return c / l;
}

void WireWidth(string sig, real w)
{
  // ermitteln der min-max Leiterbahnbreite
  if (w < width_min[n])  width_min[n] = w;
  if (w > width_max[n])  width_max[n] = w;
}

// Adjust this to be imax Copper. Then, add imax Ink.
real IMaxCopper(real width)
{
  return (width == 0) ? 0 : 5.25 * sqrt((Ink * width * (Ink + width)) * k[int(trunc(width))]);
}

// For ink, use what we calculated before, using tref = 80C.
real IMaxInk(real width)
{
  // The equation is complicated, but that's what we get. Tref is 80C.
  return (width == 0) ? 0 : sqrt(55/(2799.7*pow((width*1000/25.4),(-1.139))));
}

// Calculate resistance given a length, width, and material type.
real CalcResistance(string material, real length, real width) {
    real r = 1;

    if (material == "copper") {
        r = (0.0174 * length / (Cu * width));
    }
    else {
        if (material == "ink") {
            r = (0.96 * length / (Ink * width)) / 1000;
        }
    }
    return r;
}


// --------------------------------------- EXECUTION SCRIPT

if (board) board(B) {
    help();


   sprintf(h, "%s\n", EAGLE_SIGNATURE);
   header += h;
   sprintf(h, "List of signals with length and its resistance and max. current\n");
   header += h;
   sprintf(h, "exported from %s\nat %s\n", B.name, t2string(time()));
   header += h;


   B.signals(S) {
     real length = 0;
     wire_length_total = 0;
     res_total_cu = 0;
     res_total_ink = 0;

     width_min[n] = 32000; // I believe this is the maximum possible width
     width_max[n] = 0;

     S.wires(W) {
       if (W.layer < 17) {           // nur Kupfer-Layer
          if (W.arc) {
             length = ArcLength(W.arc.angle1, W.arc.angle2, u2mm(W.arc.radius));
             }

          else {
             length = WireLength(u2mm(W.x2), u2mm(W.x1), u2mm(W.y2), u2mm(W.y1));
             }

          wire_length_total += length;
          res_total_cu += CalcResistance("copper", length, u2mm(W.width));
          res_total_ink += CalcResistance("ink", length, u2mm(W.width));

          WireWidth(S.name, u2mm(W.width));
          }
       }
     if (wire_length_total != 0) {
        signal[n] = S.name;
        wire_length[n] = wire_length_total;
        resistance_copper[n] = res_total_cu;
        resistance_ink[n] = res_total_ink;
        ++n;
        }
     }
   sort(n, index, wire_length);

   // "A" here is misleading - it's the cross-sectional area, not total area.
   sprintf(h, "Signal\tLength [mm]\tR ink [Ohm]\tw min [mm]\tw max [mm]\tImax_ink [A]");
   data[0] = h;
   t = 1;

   for (int i = 0; i < n; ++i) {
       string R_copper;
       string R_ink;

       // Calculates resistance. These constant names are rough times.
       if (width_min[index[i]]) {
          // The constants used in this calculation are a bit opaque, but digging shows that it just uses R = pL/A, where p is 174/(10*1000). The value 174 is the resistivity of annealed copper at room temperature (~23C), given the temperature coefficient of annealed copper. See http://hyperphysics.phy-astr.gsu.edu/hbase/Tables/rstiv.html

          sprintf(R_copper, "%7.2f", resistance_copper[index[i]]);

          sprintf(R_ink, "%7.2f", resistance_ink[index[i]]);
          }

       sprintf(h, "%s\t%7.3f\t%s\t%6.3f\t%6.3f\t%6.2f", signal[index[i]], wire_length[index[i]], R_ink, width_min[index[i]], width_max[index[i]], IMaxInk(width_min[index[i]]));
       data[t] = h;

       if (!width_min[index[i]]) {
          note = 1;
          sprintf( h, " ***");
          data[t] += h;
          }
       t++;
       }

   dialog();
   }

else {
   dlgMessageBox("\n    Start this ULP in a Board     \n");
   exit (0);
}
