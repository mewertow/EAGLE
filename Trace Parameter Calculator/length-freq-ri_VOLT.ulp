#usage "<b>This ULP creates a list of all signals with various data</b>\n"
       "<p>"
       "Creates a list of all signals of a board, together "
       "with their maximum frequency, length, area, resistance, "
       "minimum and maximum width and maximum current."
       "<p>"
       "This calculation is very simple - it uses minimum Width "
       "in a signal for calculating the resistance. Take note "
       "that the values, then, of R [mOhm] and Imax [A] may not "
       "be representative of the actual value if there are multiple "
       "widths in the signal. "

       "<p>"
       "Parallel tracks and polygons are not taken into consideration."
       "<p>"
       "<author>Author: support@voltera.io</author>"

// THIS PROGRAM IS PROVIDED AS IS AND WITHOUT WARRANTY OF ANY KIND, EXPRESSED OR IMPLIED

/*  German description:
 "Dieses ULP berechnet alle Signallaengen eines Layouts<p>"
 "(nur Layer 1 bis 16) und die zugehoerige Frequenz (f=c/l) "
 "und erzeugt eine Textdatei length-ri.txt, die alle Signale nach "
 "Frequenz bzw Laenge sortiert enthaelt.<p>"
 "Bei der Frequenzberechnung handelt es sich um eine ganz einfache "
 "Umrechnung, die eine erste Abschaetzung bzgl. Stoerstrahlung erlaubt.<p>"
 "Zusaetzlich wird die minimale und maximale Leiterbahnbreite ermittelt "
 "und die daraus resultierende Strombelastung.<p>"
 "Bei der Widerstands- und Strombelastbarkeits-Berechnung wird die "
 "minimale Leiterbahnbreite herangezogen.<p>"
 "Es wird auch keine eine Parallelführung bzw. Fläche (Polygon) "
 "berücksichtigt.<p>"
 "A. Zaffran 05.04.2000 alf@cadsoft.de<p>"
*/

// --------------------------------------- CONSTANTS

string Help = usage;
string HButton = "&Help";
string SButton = "&Save";

real f, WLtotal;
int index[];

    // ** aus "Mechanik der Elektronik"
    // mm  <1  1  2  3  4  5  6  7  8  9 10 11 12 13 mm Leiterbreite bei 35 um Cu

// Leave this in for now, but make a new method for ink.
real k[] = { 9, 8.8, 6, 4, 3.2, 2.9, 2.9, 2.9, 2.9, 2.9, 2.9, 2.9, 2.9, 2.9, 2.9 };

    //               _______________________
    //  Imax ~ 5.25 V [d x b x (d + b)] x k      ||  (tL ~60°)
    //
    //  d = um Cu-Kaschierung
    //  b = Breite mm
    //  k = Korrekturwert aus Tabelle      02.02.2000 alf
    //  ** aus "Mechanik der Elektronik"

real Cu = 0.035;  // 35 um Cu Kaschierung
real Ink = 0.100; // 85 um standard ink thickness


real Length[], Freq[], Widthmin[], Widthmax[];
string Signal[];

real c = 299800;   // Lichtgechwindigkeit Vakuum in [km/s]

int n = 0;
int t;
string data[];
string h;
string header;
int note = 0;

// --------------------------------------- METHODS

void help(void) {
  dlgMessageBox(Help, "Ok");
  return;
}

void dialog(void)
{
  int select = 0;
  int Result = dlgDialog("Signal Wire Parameters in Board") {
    dlgLabel(header);
    string lab;
    sprintf(lab, " Ink thickness = %.3f mm, Copper thickness - %.3f mm", Ink, Cu);
    dlgLabel(lab);
    dlgListView("", data, select);
    // dlgHBoxLayout {
    //     dlgLabel
    // }
    dlgStretch(0);
    dlgHBoxLayout {
      dlgStretch(1);
      dlgPushButton("+&Save") {
        board(B) {
          string FileName = dlgFileSave("Save list", filesetext(B.name, ".txt"));
          if (FileName) {
             output (FileName, "wt") {
               printf("%s", header);
               for (int x = 0; x < t; x++)
                   printf("%s\n", data[x]);
               if (note) {
                  sprintf( h, "\n ***  note wire width.\n");
                  data[t]  += h;
                  t++;
                  }
               }
             }
          }
        }
      dlgPushButton("-Close") dlgReject();
      }
    };
  if (!Result)
     exit(0);
}

real WireLength(real x1, real x2, real y1, real y2)
{
  return sqrt(pow(x2 - x1, 2) + pow(y2 - y1, 2));
}

real ArcLength(real ang1, real ang2, real radius)
{
  return radius  * 2 * PI / 360 * (ang2 - ang1);
}

real Frequency(real c, real l)
{
  return c / l;
}

void WireWidth(string sig, real w)
{
  // ermitteln der min-max Leiterbahnbreite
  if (w < Widthmin[n])  Widthmin[n] = w;
  if (w > Widthmax[n])  Widthmax[n] = w;
}

// Adjust this to be imax Copper. Then, add imax Ink.
real imax(real width)
{
  return (width == 0) ? 0 : 5.25 * sqrt((Ink * width * (Ink + width)) * k[int(trunc(width))]);
}


// --------------------------------------- EXECUTION SCRIPT

if (board) board(B) {
    help();


   sprintf(h, "%s\n", EAGLE_SIGNATURE);
   header += h;
   sprintf(h, "List of signals with length and its max. frequency / current\n");
   header += h;
   sprintf(h, "exported from %s\nat %s\n", B.name, t2string(time()));
   header += h;

   B.signals(S) {
     WLtotal = 0;
     Widthmin[n] = 32000;
     Widthmax[n] = 0;
     S.wires(W) {
       if (W.layer < 17) {           // nur Kupfer-Layer
          if (W.arc) {
             WLtotal += ArcLength(W.arc.angle1, W.arc.angle2, u2mm(W.arc.radius));
             }
          else {
             WLtotal += WireLength(u2mm(W.x2), u2mm(W.x1), u2mm(W.y2), u2mm(W.y1));
             }
          WireWidth(S.name, u2mm(W.width));
          }
       }
     if (WLtotal != 0) {
        Signal[n] = S.name;
        Length[n] = WLtotal;
        Freq[n] = Frequency(c, WLtotal);
        ++n;
        }
     }
   sort(n, index, Freq);

   // "A" here is misleading - it's the cross-sectional area, not total area.
   sprintf(h, "Signal\tf max. [MHz]\tl [mm]\tA [mm2]\tR copper [mOhm]\tR ink [Ohm]\tw min [mm]\tw max [mm]\tImax [A]");
   data[0] = h;
   t = 1;

   for (int i = 0; i < n; ++i) {
       real mm2_copper = Widthmin[index[i]] * Cu;
       real mOhm_copper = 0;
       string R_copper;

       real mm2_ink = Widthmin[index[i]] * Ink;
       real Ohm_ink = 0;
       string R_ink;

       // Calculates resistance. These constant names are rough times.
       if (Widthmin[index[i]]) {
          // The constants used in this calculation are a bit opaque, but digging shows that it just uses R = pL/A, where p is 174/(10*1000). The value 174 is the resistivity of annealed copper at room temperature (~23C), given the temperature coefficient of annealed copper. See http://hyperphysics.phy-astr.gsu.edu/hbase/Tables/rstiv.html

          //Copper, constant is in mOhm.mm
          mOhm_copper  = (0.0174 * Length[index[i]]) / ( Cu * Widthmin[index[i]]);

          sprintf(R_copper, "%7.2f", mOhm_copper);

          // Here, we just use sheet resistance of ink (12 mOhm/sq)
          Ohm_ink  = (12 * Length[index[i]]) / (Widthmin[index[i]]) / 1000;

          sprintf(R_ink, "%7.2f", Ohm_ink);
          }

       sprintf(h, "%s\t%10.2f\t%7.3f\t%4.3f\t%s\t%s\t%6.3f\t%6.3f\t%6.2f", Signal[index[i]], Freq[index[i]], Length[index[i]], mm2_ink, R_copper, R_ink, Widthmin[index[i]], Widthmax[index[i]], imax(Widthmin[index[i]]));
       data[t] = h;

       if (!Widthmin[index[i]]) {
          note = 1;
          sprintf( h, " ***");
          data[t] += h;
          }
       t++;
       }

   dialog();
   }

else {
   dlgMessageBox("\n    Start this ULP in a Board     \n");
   exit (0);
}
